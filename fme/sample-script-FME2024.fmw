FME workspace sample-script-FME2024.fmw

Parameters:
- parametersFile = $(FME_MF_DIR_USERTYPED)\parameters.json   # "" Select a File

Creator
    GEOMTYPE = Geometry Object
    NUM = 1
    CREATED -> Read_Parameters [INITIATOR]
Read_Parameters: FeatureReader
    ATTRIBUTES = parameters,"Request,FolderOut,OrderGuid,OrderLabel,ClientGuid,ClientName,OrganismGuid,OrganismName,ProductGuid,ProductLabel,Parameters.FORMAT,Parameters.PROJECTION,Parameters.LAST_ORDER,Parameters.REMARK,Parameters.CLIENT_LANG"
    ATTR_ACCUM_MODE = Only Use Result
    COMBINE_GEOM = Use Result
    DATASET = $(parametersFile)
    FORMAT = GEOJSON
    GEOJSON_FLATTEN_MODE = ALL_LEVELS
    GEOJSON_USE_BASENAME_AS_DEFAULT_FEATURE_TYPE = Yes
    GEOJSON_USE_SEARCH_ENVELOPE = NO
    GEOMETRY_TYPES = parameters,""",fme_area"""
    INTERACT = NONE
    ORDER_RESULTS = No
    OUTPUT_ADD_SCHEMA_ATTRIBUTES = NO
    OUTPUT_FEATURES_DISPLAY = Schema and Data Features
    parameters -> set_var_FolderOut
    parameters -> FeatureWriter [text_line]
set_var_FolderOut: VariableSetter
    SCOPE = Global
    VALUE = @Value(FolderOut)
    VARNAME = FolderOut
    -> set_var_OrderLabel
set_var_OrderLabel: VariableSetter
    SCOPE = Global
    VALUE = @Value(OrderLabel)
    VARNAME = OrderLabel
    -> Set_var_format
Set_var_format: VariableSetter
    SCOPE = Global
    VALUE = @Value(Parameters.FORMAT)
    VARNAME = Format
    -> set_var_ProjectionEPSG
set_var_ProjectionEPSG: VariableSetter
    SCOPE = Global
    VALUE = FME_CONDITIONAL:DEFAULT_VALUE''BOOL_OP;OR;COMPOSITE_TEST;1;TEST @Value(Parameters.PROJECTION) = SWITZERLAND95'EPSG:2056'BOOL_OP;OR;COMPOSITE_TEST;1;TEST @Value(Parameters.PROJECTION) = SWITZERLAND'EPSG:21781'FME_NUM_CONDITIONS3___
    VARNAME = ProjectionEPSG
    -> Reprojector
Note: Reproject perimeter to same CRS as input data (EPSG:2056)
Reprojector
    DEST = EPSG:2056
    INTERPOLATION_TYPE = ,NearestNeighbor
    RASTER_CELL_SIZE_LOOKUP = ,PreserveCells
    RASTER_TOLERANCE = 0.0
    SOURCE = EPSG:4326
    INTERPOLATION_TYPE_NAME = Nearest Neighbor
    RASTER_CELL_SIZE = Preserve Cells
    REPROJECTED -> Read_Data [INITIATOR]
Note: Read data that intersect with the perimeter
Read_Data: FeatureReader
    ATTRIBUTES = tlmregio_buildings_building,"id,objorig,dateofchng,uuid,objval,objorig_year,fid"
    ATTR_ACCUM_MODE = Only Use Result
    COMBINE_GEOM = Use Result
    DATASET = $(FME_MF_DIR_USERTYPED)\data\swissTLMRegio_Buildings_2056.zip
    FEATURETYPES = tlmregio_buildings_building
    FORMAT = OGCGEOPACKAGE
    GEOMETRY_TYPES = tlmregio_buildings_building,""",fme_area"""
    INTERACT = INTERSECTS
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    tlmregio_buildings_building -> Retrieve_FolderOut
Retrieve_FolderOut: VariableRetriever
    SCOPE = Global
    VALUE_ATTR = FolderOut
    VARNAME = FolderOut
    -> Retrieve_OrderLabel
Retrieve_OrderLabel: VariableRetriever
    SCOPE = Global
    VALUE_ATTR = OrderLabel
    VARNAME = OrderLabel
    -> Retrieve_Format
Retrieve_Format: VariableRetriever
    SCOPE = Global
    VALUE_ATTR = Format
    VARNAME = Format
    -> Retrieve_ProjectionEPSG
Retrieve_ProjectionEPSG: VariableRetriever
    SCOPE = Global
    VALUE_ATTR = ProjectionEPSG
    VARNAME = ProjectionEPSG
    -> Reprojector_2
Note: Reproject data to desired projection
Reprojector_2
    DEST = @Value(ProjectionEPSG)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Filter_by_format
Filter_by_format: TestFilter
    DEFAULT_VALUE = <UNFILTERED>
    PASSED_TEST_GROUP_OUTPUT = FIRST
    TEST_LIST = "BOOL_OP,OR,COMPOSITE_TEST,""""""1"""""",TEST_CLAUSE,TEST @Value(Format) = SHP",shapefile,"BOOL_OP,OR,COMPOSITE_TEST,""""""1"""""",TEST_CLAUSE,TEST @Value(Format) = GPKG",geopackage,"BOOL_OP,OR,COMPOSITE_TEST,""""""1"""""",TEST_CLAUSE,TEST @Value(Format) = GEOJSON",geojson,"BOOL_OP,OR,COMPOSITE_TEST,""""""1"""""",TEST_CLAUSE,TEST @Value(Format) = DXF",dxf
    shapefile -> Write_Shapefile [shapefile]
    geopackage -> Write_Geopackage [geopackage]
    geojson -> Write_GeoJSON [geopackage]
    dxf -> Write_DXF [dxf]
Write_Shapefile: FeatureWriter
    DATASET = @Value(FolderOut)
    DATASET_ATTR = _dataset
    FEATURE_TYPE_LIST_ATTR = _feature_types
    FORMAT = SHAPEFILE
    SHAPEFILE_COMPRESSED_FILE = No
    SHAPEFILE_DATASET_SPLITTING = Yes
    SHAPEFILE_DATETIME_STORAGE = TIMESTAMP_STRING
    SHAPEFILE_DESTINATION_DATASETTYPE_VALIDATION = Yes
    SHAPEFILE_DIMENSION = AUTO
    SHAPEFILE_ENCODING = utf-8
    SHAPEFILE_ENFORCE_ATTRIBUTE_LIMIT = No
    SHAPEFILE_MEASURES_AS_Z = No
    SHAPEFILE_PERMIT_NONASCII_FIRST_ATTRNAME = Yes
    SHAPEFILE_REQUIRE_FIRST_ATTRNAME_ALPHA = Yes
    SHAPEFILE_SPATIAL_INDEXES = NONE
    SHAPEFILE_SURFACE_SOLID_STORAGE = PATCH
    TOTAL_FEATURES_WRITTEN_ATTR = _total_features_written
Write_Geopackage: FeatureWriter
    DATASET = @Value(FolderOut)/@Value(OrderLabel).gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = NO
    OGCGEOPACKAGE_TRANSACTION_SIZE = 5000
    OGCGEOPACKAGE_VERSION = 1.2
    OGCGEOPACKAGE_WRITE_NULLS = YES
    TOTAL_FEATURES_WRITTEN_ATTR = _total_features_written
Write_GeoJSON: FeatureWriter
    DATASET = @Value(FolderOut)/@Value(OrderLabel).geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = No
    GEOJSON_WRITER_CHARSET = UTF-8
    GEOJSON_WRITE_BOM = No
    TOTAL_FEATURES_WRITTEN_ATTR = _total_features_written
Write_DXF: FeatureWriter
    ACAD_APPEND_TO_TEMPLATEFILE = no
    ACAD_AUDIT_AND_FIX = yes
    ACAD_COORDINATE_SYSTEM_STORAGE = NATIVE INTERNAL_WKT
    ACAD_DEFAULT_ATTR_STORAGE = external_attributes
    ACAD_DESTINATION_DATASETTYPE_VALIDATION = Yes
    ACAD_OUTPUT_DEFINED_ATTRS_ONLY = yes
    ACAD_PREFER_DONUTS_AS_HATCHES = no
    ACAD_PRESERVE_TEMPLATE_PAPER_SPACE_ENTITIES = yes
    ACAD_PURGE = no
    ACAD_USE_BLOCK_NAME_FOR_CREATION = no
    ACAD_VERSION = Release2013
    ACAD_WRITE_THUMBNAIL_IMAGE = no
    DATASET = @Value(FolderOut)/@Value(OrderLabel).dxf
    DATASET_ATTR = _dataset
    FEATURE_TYPE_LIST_ATTR = _feature_types
    FORMAT = ACAD
    TOTAL_FEATURES_WRITTEN_ATTR = _total_features_written
FeatureWriter
    DATASET = @Value(FolderOut)/input_parameters.txt
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = text/plain
    TEXTLINE_OVERWRITE_FILE = YES
    TEXTLINE_WRITE_LAST_EOL = YES
    TEXTLINE_WRITE_UTF8_BOM = YES
    TOTAL_FEATURES_WRITTEN_ATTR = _total_features_written
